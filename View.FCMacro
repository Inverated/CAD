#!/usr/bin/env python3
"""
View.FCMacro - Interactive view selector for Solar Proa designs

This macro provides a dialog to select different camera views and projection modes
for the currently open FreeCAD document.

Features:
- Standard views (Isometric, Front, Top, Right, etc.)
- Specialized views (Sail, Interior, Mast, Cockpit, Below deck)
- Orthographic vs Perspective projection toggle
- Does not load or modify any design - works on current document

Usage:
1. Open a design in FreeCAD
2. Run this macro (Macro > Macros > View > Execute)
3. Select desired view and projection mode
4. Click "Apply View"
"""

import FreeCAD
import sys

# Check if GUI is available
if not FreeCAD.GuiUp:
    print("ERROR: This macro requires FreeCAD GUI mode")
    sys.exit(1)

import FreeCADGui
from PySide import QtGui, QtCore

class ViewDialog(QtGui.QDialog):
    """Dialog for selecting view and projection mode"""
    
    def __init__(self):
        super(ViewDialog, self).__init__()
        self.setWindowTitle("Solar Proa - View Selector")
        self.setMinimumWidth(450)
        self.setMinimumHeight(400)
        
        layout = QtGui.QVBoxLayout()
        
        # Info label
        info = QtGui.QLabel("Select view and projection for the current document")
        info.setStyleSheet("color: #666; font-style: italic; padding: 5px;")
        layout.addWidget(info)
        
        # Standard views group
        standard_group = QtGui.QGroupBox("Standard Views")
        standard_layout = QtGui.QVBoxLayout()
        
        self.view_list = QtGui.QListWidget()
        self.view_list.setSelectionMode(QtGui.QAbstractItemView.SingleSelection)
        
        # Define available views with descriptions
        self.views = [
            ("Isometric", "viewIsometric", "3D isometric view"),
            ("Front", "viewFront", "Front elevation view"),
            ("Rear", "viewRear", "Rear elevation view"),
            ("Top", "viewTop", "Top plan view"),
            ("Bottom", "viewBottom", "Bottom view"),
            ("Left", "viewLeft", "Left side view"),
            ("Right", "viewRight", "Right side view"),
        ]
        
        for name, _, description in self.views:
            item = QtGui.QListWidgetItem(f"{name} - {description}")
            item.setData(QtCore.Qt.UserRole, name)
            self.view_list.addItem(item)
        
        # Set default to Isometric
        self.view_list.setCurrentRow(0)
        
        standard_layout.addWidget(self.view_list)
        standard_group.setLayout(standard_layout)
        layout.addWidget(standard_group)
        
        # Specialized views group
        specialized_group = QtGui.QGroupBox("Specialized Views (Solar Proa)")
        specialized_layout = QtGui.QVBoxLayout()
        
        self.specialized_list = QtGui.QListWidget()
        self.specialized_list.setSelectionMode(QtGui.QAbstractItemView.SingleSelection)
        
        self.specialized_views = [
            ("Sail View", "sail", "View focused on sail configuration"),
            ("Interior View", "interior", "View inside the hull"),
            ("Mast View", "mast", "Close-up view of mast and rigging"),
            ("Cockpit View", "cockpit", "View of cockpit area"),
            ("Below Deck", "below", "View below deck level"),
        ]
        
        for name, key, description in self.specialized_views:
            item = QtGui.QListWidgetItem(f"{name} - {description}")
            item.setData(QtCore.Qt.UserRole, key)
            self.specialized_list.addItem(item)
        
        specialized_layout.addWidget(self.specialized_list)
        specialized_group.setLayout(specialized_layout)
        layout.addWidget(specialized_group)
        
        # Connect list selections to deselect the other list
        self.view_list.itemSelectionChanged.connect(
            lambda: self.specialized_list.clearSelection()
        )
        self.specialized_list.itemSelectionChanged.connect(
            lambda: self.view_list.clearSelection()
        )
        
        # Projection mode group
        projection_group = QtGui.QGroupBox("Projection Mode")
        projection_layout = QtGui.QHBoxLayout()
        
        self.ortho_radio = QtGui.QRadioButton("Orthographic")
        self.ortho_radio.setChecked(True)
        self.ortho_radio.setToolTip("Parallel projection (no perspective distortion)")
        projection_layout.addWidget(self.ortho_radio)
        
        self.persp_radio = QtGui.QRadioButton("Perspective")
        self.persp_radio.setToolTip("Perspective projection (realistic depth)")
        projection_layout.addWidget(self.persp_radio)
        
        projection_group.setLayout(projection_layout)
        layout.addWidget(projection_group)
        
        # Fit to view checkbox
        self.fit_checkbox = QtGui.QCheckBox("Fit all objects in view")
        self.fit_checkbox.setChecked(True)
        self.fit_checkbox.setToolTip("Zoom to show all objects")
        layout.addWidget(self.fit_checkbox)
        
        # Buttons
        button_layout = QtGui.QHBoxLayout()
        apply_btn = QtGui.QPushButton("Apply View")
        apply_btn.clicked.connect(self.accept)
        apply_btn.setDefault(True)
        button_layout.addWidget(apply_btn)
        
        cancel_btn = QtGui.QPushButton("Cancel")
        cancel_btn.clicked.connect(self.reject)
        button_layout.addWidget(cancel_btn)
        
        layout.addLayout(button_layout)
        
        self.setLayout(layout)
    
    def get_selected_view(self):
        """Get the selected view type and method"""
        # Check standard views first
        selected_items = self.view_list.selectedItems()
        if selected_items:
            view_name = selected_items[0].data(QtCore.Qt.UserRole)
            # Find the method for this view
            for name, method, _ in self.views:
                if name == view_name:
                    return ("standard", method, view_name)
        
        # Check specialized views
        selected_items = self.specialized_list.selectedItems()
        if selected_items:
            view_key = selected_items[0].data(QtCore.Qt.UserRole)
            return ("specialized", view_key, view_key)
        
        # Default to isometric
        return ("standard", "viewIsometric", "Isometric")
    
    def is_orthographic(self):
        """Check if orthographic projection is selected"""
        return self.ortho_radio.isChecked()
    
    def should_fit_all(self):
        """Check if fit all is enabled"""
        return self.fit_checkbox.isChecked()


def set_sail_view(view):
    """Set camera to view the sail configuration"""
    # Position camera to show sails clearly
    # Adjust these values based on typical proa dimensions
    from FreeCAD import Base
    
    # Camera position: slightly elevated and to the side
    camera_pos = Base.Vector(5000, -3000, 2000)
    camera_target = Base.Vector(0, 0, 1500)
    
    view.viewPosition(camera_pos, camera_target, 0)
    view.fitAll()


def set_interior_view(view):
    """Set camera to view inside the hull"""
    from FreeCAD import Base
    
    # Position camera inside the vaka looking forward
    camera_pos = Base.Vector(-1000, 0, 800)
    camera_target = Base.Vector(2000, 0, 800)
    
    view.viewPosition(camera_pos, camera_target, 0)


def set_mast_view(view):
    """Set camera to close-up view of mast and rigging"""
    from FreeCAD import Base
    
    # Position camera to focus on mast area
    camera_pos = Base.Vector(2000, -2000, 3000)
    camera_target = Base.Vector(0, 0, 2000)
    
    view.viewPosition(camera_pos, camera_target, 0)


def set_cockpit_view(view):
    """Set camera to view the cockpit area"""
    from FreeCAD import Base
    
    # Position camera at typical helmsman position
    camera_pos = Base.Vector(-500, 0, 1200)
    camera_target = Base.Vector(1500, 0, 800)
    
    view.viewPosition(camera_pos, camera_target, 0)


def set_below_view(view):
    """Set camera to view below deck level"""
    from FreeCAD import Base
    
    # Position camera below deck looking up
    camera_pos = Base.Vector(0, -2000, 200)
    camera_target = Base.Vector(0, 0, 800)
    
    view.viewPosition(camera_pos, camera_target, 0)


def apply_view(view_type, view_method, view_name, is_ortho, fit_all):
    """Apply the selected view to the active document"""
    
    # Check if there's an active document
    if not FreeCAD.ActiveDocument:
        QtGui.QMessageBox.warning(
            None,
            "No Document",
            "No document is currently open.\n\n"
            "Please open a design file first."
        )
        return False
    
    # Get the active view
    view = FreeCADGui.activeDocument().activeView()
    if not view:
        QtGui.QMessageBox.warning(
            None,
            "No View",
            "Could not access the active view."
        )
        return False
    
    try:
        # Apply the view
        if view_type == "standard":
            # Call the standard FreeCAD view method
            method = getattr(view, view_method)
            method()
        elif view_type == "specialized":
            # Call our specialized view function
            if view_method == "sail":
                set_sail_view(view)
            elif view_method == "interior":
                set_interior_view(view)
            elif view_method == "mast":
                set_mast_view(view)
            elif view_method == "cockpit":
                set_cockpit_view(view)
            elif view_method == "below":
                set_below_view(view)
        
        # Set projection mode
        if is_ortho:
            view.setCameraType("Orthographic")
        else:
            view.setCameraType("Perspective")
        
        # Fit all if requested
        if fit_all:
            view.fitAll()
        
        print(f"✓ Applied view: {view_name}")
        print(f"  Projection: {'Orthographic' if is_ortho else 'Perspective'}")
        
        return True
        
    except Exception as e:
        QtGui.QMessageBox.critical(
            None,
            "View Error",
            f"Failed to apply view:\n{str(e)}"
        )
        print(f"✗ Error applying view: {e}")
        return False


# Main execution
if __name__ == "__main__":
    # Show dialog
    dialog = ViewDialog()
    if dialog.exec_() != QtGui.QDialog.Accepted:
        print("View selection cancelled")
    else:
        view_type, view_method, view_name = dialog.get_selected_view()
        is_ortho = dialog.is_orthographic()
        fit_all = dialog.should_fit_all()
        
        apply_view(view_type, view_method, view_name, is_ortho, fit_all)
